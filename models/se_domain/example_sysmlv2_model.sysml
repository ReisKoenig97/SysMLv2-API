package example {

  part def example_part {

    attribute id =  "example-model-id"; 
    attribute name =  "My Model"; 
    attribute description =  "This is a example description"; 
    attribute type =  "model"; 
  }
}
